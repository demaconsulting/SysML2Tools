// General view test model — used by Phase 4 layout strategy tests and end-to-end rendering tests.

package GeneralViewTest {

    part def ComponentA {
    }

    part def ComponentB specializes ComponentA {
    }

    view def GeneralView {
    }
}
